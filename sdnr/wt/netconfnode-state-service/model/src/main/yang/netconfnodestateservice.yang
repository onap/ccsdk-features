module netconfnode-state {

    yang-version 1;
    namespace "urn:opendaylight:params:xml:ns:yang:netconfnode-state";
    prefix "netconfnode-state";

    import data-provider { prefix "data-provider"; }

    description
        "sdnr-wt-netconfnode-state-service Api Module";

    revision "2019-10-11" {
        description
            "Initial revision";
    }

    container fault-notification {
        description
            "Handle fault problem notification of a network-element";
        uses data-provider:object-change-reference;
        uses data-provider:fault;
    }
    container attribute-change-notification {
        description
            "Handle  attribute change notification of a network-element";
            uses data-provider:object-change-reference;
            uses data-provider:attribute-change;
    }
    rpc push-fault-notification {
        description
            "Forward fault problem notification of a network-element";
        input {
            uses data-provider:object-change-reference;
            uses data-provider:fault;
        }
    }
    rpc push-attribute-change-notification {
        description
            "Forward attribute change notification of a network-element";
        input {
            uses data-provider:object-change-reference;
            uses data-provider:attribute-change;
        }
    }

    rpc get-status {
        description
                "Returns status information";

        output {
            list status {
                description "Provides a key value list with status information";
                key key;
                leaf key {
                    type string;
                }
                leaf value {
                    type string;
                }
            }
        }
    }
}
