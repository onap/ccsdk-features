module netconfnode-state {

  yang-version 1;
  namespace "urn:opendaylight:params:xml:ns:yang:netconfnode-state";
  prefix netconfnode-state;

  import data-provider {
    prefix data-provider;
  }

  organization
    "highstreet technologies GmbH";
  contact
    "Web:   <https://highstreet-technologies.com>
     ONAP:  <https://wiki.onap.org/display/DW/ODLUX+DB+API>";

  description
    "netconfnode-state-service Api Module

     Copyright 2019 highstreet technologies GmbH Intellectual Property.
     All rights reserved.

     Licensed under the Apache License, Version 2.0 (the 'License');
     you may not use this file except in compliance with the License.
     You may obtain a copy of the License at

       http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2019-10-11 {
    description
      "Initial revision";
    reference
      "https://jira.onap.org/browse/SDNC-877";
  }

  container fault-notification {
    description
      "Handle fault problem notification of a network-element";
    uses data-provider:object-change-reference;
    uses data-provider:fault;
  }
  container attribute-change-notification {
    description
      "Handle  attribute change notification of a network-element";
    uses data-provider:object-change-reference;
    uses data-provider:attribute-change;
  }

  rpc push-fault-notification {
    description
      "Forward fault problem notification of a network-element";
    input {
      uses data-provider:object-change-reference;
      uses data-provider:fault;
    }
  }

  rpc push-attribute-change-notification {
    description
      "Forward attribute change notification of a network-element";
    input {
      uses data-provider:object-change-reference;
      uses data-provider:attribute-change;
    }
  }

  rpc get-status {
    description
      "Returns status information";
    output {
      list status {
        key "key";
        leaf key {
          type string;
          description
            "A unique identifier for the status.";
        }
        leaf value {
          type string;
          description
            "The value corresponding to the key.";
        }
        description
          "Provides a key value list with status information";
      }
    }
  }
}
