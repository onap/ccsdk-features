module websocketmanager {

  yang-version 1;
  namespace "urn:opendaylight:params:xml:ns:yang:websocketmanager";
  prefix websocketmanager;

  import ietf-yang-types {
    prefix yang;
  }
  organization
    "highstreet technologies GmbH";
  contact
    "Web:   <https://highstreet-technologies.com>
     ONAP:  <https://wiki.onap.org/display/DW/SDN-R+Websocketmanager+Upgrade>";

  description
    "Websocketmanager Api Module

     Copyright 2021 highstreet technologies GmbH Intellectual Property.
     All rights reserved.

     Licensed under the Apache License, Version 2.0 (the 'License');
     you may not use this file except in compliance with the License.
     You may obtain a copy of the License at

       http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2021-03-22 {
    description
      "Initial revision";
  }

  notification items-dropped-notification {
      uses items-dropped-notification-g;
      description "none";
  }
  grouping items-dropped-notification-g {
      leaf amount {
          type uint32;
          default 0;
          description "Counts of notifications that were dropped.";
      }
      description "To be sent when notifications were dropped in fact of a set ratio limit.";
  }
}
