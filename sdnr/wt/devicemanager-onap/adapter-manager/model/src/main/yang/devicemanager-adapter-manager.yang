module devicemanager-adapter-manager {

  yang-version 1;
  namespace "urn:opendaylight:params:xml:ns:yang:devicemanager-adapter-manager";
  prefix devicemanager-adapter-manager;

  organization
    "highstreet technologies GmbH";
  contact
    "Web:   <https://highstreet-technologies.com>";

  description
    "DeviceManager adapter-manager Api Module

     Copyright 2020 highstreet technologies GmbH Intellectual Property.
     All rights reserved.

     Licensed under the Apache License, Version 2.0 (the 'License');
     you may not use this file except in compliance with the License.
     You may obtain a copy of the License at

       http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2020-08-19 {
    description
      "Initial revision";
    reference
      "https://jira.onap.org/browse/CCSDK-2573";
  }
}
