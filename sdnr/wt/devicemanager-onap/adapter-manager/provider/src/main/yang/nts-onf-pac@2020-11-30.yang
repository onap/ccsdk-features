module nts-onf-pac {
  yang-version 1.1;
  namespace "urn:o-ran-sc:params:xml:ns:yang:nts:onf";
  prefix nts-onf;

  import nts-common {
    prefix ntsc;
  }

  organization
    "O-RAN-SC";
  contact
    " Web: <https://wiki.o-ran-sc.org/display/SIM/SIM>
        Editors:
        Alex Stancu <mailto:alexandru.stancu@highstreet-technologies.com>
        Adrian Lita <mailto:adrian.lita@highstreet-technologies.com>
        Martin Skorupski <mailto:martin.skorupski@highstreet-technologies.com>";
  description
    "This module contains YANG definitions for the Network Topology Simulator - ONF extensions.";

  revision 2020-11-30 {
    description
      "Cleared revision for nts-common import.";
    reference
      "ONF implementation";
  }
  revision 2020-10-26 {
    description
      "Initial revision for the Network Topology Simulator - Next Generation";
    reference
      "ONF implementation";
  }

  identity NTS_FUNCTION_TYPE_ONF_CORE_MODEL_1_2 {
    base ntsc:NTS_FUNCTION_TYPE_BASE;
    description
      "The simulated network function implements ONF Core Model version 1.2 YANG models.";
    reference
      "nts-ng-onf-core-1-2";
  }

  identity NTS_FUNCTION_TYPE_ONF_CORE_MODEL_1_4 {
    base ntsc:NTS_FUNCTION_TYPE_BASE;
    description
      "The simulated device implements ONF Core Model version 1.4 YANG models.";
    reference
      "nts-ng-onf-core-1-4";
  }
}
