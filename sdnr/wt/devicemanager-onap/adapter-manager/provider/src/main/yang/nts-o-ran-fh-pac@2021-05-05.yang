module nts-o-ran-fh-pac {
  yang-version 1.1;
  namespace "urn:o-ran-sc:params:xml:ns:yang:nts:o-ran-fh";
  prefix nts-o-ran-fh;

  import nts-common {
    prefix ntsc;
  }

  organization
    "O-RAN-SC";
  contact
    " Web: <https://wiki.o-ran-sc.org/display/SIM/SIM>
        Editors:
        Alex Stancu <mailto:alexandru.stancu@highstreet-technologies.com>
        Adrian Lita <mailto:adrian.lita@highstreet-technologies.com>
        Martin Skorupski <mailto:martin.skorupski@highstreet-technologies.com>";
  description
    "This module contains YANG definitions for the Network Topology Simulator - O-RAN extensions.";

  revision 2021-05-05 {
    description
      "Changed name to o-ran-fh.";
    reference
      "O-RAN-FH implementation";
  }
  revision 2020-11-30 {
    description
      "Cleared revision for nts-common import.";
    reference
      "O-RAN implementation";
  }
  revision 2020-10-26 {
    description
      "Initial revision for the Network Topology Simulator - Next Generation";
    reference
      "O-RAN implementation";
  }

  identity NTS_FUNCTION_TYPE_O_RAN_FH {
    base ntsc:NTS_FUNCTION_TYPE_BASE;
    description
      "The simulated network function implements O-RAN FrontHaul (O1) YANG models.";
    reference
      "nts-ng-o-ran-fh";
  }
}
