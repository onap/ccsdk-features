module nts-development-pac {
  yang-version 1.1;
  namespace "urn:o-ran-sc:params:xml:ns:yang:nts:development";
  prefix nts-dev;

  import nts-common {
    prefix ntsc;
  }

  organization
    "O-RAN-SC";
  contact
    " Web: <https://wiki.o-ran-sc.org/display/SIM/SIM>
        Editors:
        Alex Stancu <mailto:alexandru.stancu@highstreet-technologies.com>
        Adrian Lita <mailto:adrian.lita@highstreet-technologies.com>
        Martin Skorupski <mailto:martin.skorupski@highstreet-technologies.com>";
  description
    "This module contains YANG definitions for the Network Topology Simulator - Development extensions.";

  revision 2021-05-05 {
    description
      "Added sepparate NTS_FUNCTION_TYPE_DEV/SANDBOX types.";
    reference
      "Development implementation";
  }
  revision 2020-11-30 {
    description
      "Cleared revision for nts-common import.";
    reference
      "Development implementation";
  }
  revision 2020-10-26 {
    description
      "Initial revision for the Network Topology Simulator - Next Generation";
    reference
      "Development implementation";
  }

  identity NTS_FUNCTION_TYPE_DEV {
    base ntsc:NTS_FUNCTION_TYPE_BASE;
    description
      "The simulated network function implements a dev YANG model.";
    reference
      "nts-ng-dev";
  }

  identity NTS_FUNCTION_TYPE_SANDBOX {
    base ntsc:NTS_FUNCTION_TYPE_BASE;
    description
      "The simulated network function implements a dev sandbox YANG model.";
    reference
      "nts-ng-sandbox";
  }
}
