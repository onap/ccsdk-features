module nts-o-ran-o1-pac {
  yang-version 1.1;
  namespace "urn:o-ran-sc:params:xml:ns:yang:nts:o-ran-o1";
  prefix nts-o-ran-o1;

  import nts-common {
    prefix ntsc;
  }

  organization
    "O-RAN-SC";
  contact
    " Web: <https://wiki.o-ran-sc.org/display/SIM/SIM>
        Editors:
        Alex Stancu <mailto:alexandru.stancu@highstreet-technologies.com>
        Adrian Lita <mailto:adrian.lita@highstreet-technologies.com>
        Martin Skorupski <mailto:martin.skorupski@highstreet-technologies.com>";
  description
    "This module contains YANG definitions for the Network Topology Simulator - O-RAN O1 interface.";

  revision 2021-05-05 {
    description
      "Initial revision for the Network Topology Simulator - Next Generation";
    reference
      "O-RAN-O1 implementation";
  }

  identity NTS_FUNCTION_TYPE_O_RAN_O1 {
    base ntsc:NTS_FUNCTION_TYPE_BASE;
    description
      "The simulated network function implements a O-RAN O1 interface YANG model.";
    reference
      "nts-ng-o-ran-o1";
  }
}
