module nts-x-ran-pac {
  yang-version 1.1;
  namespace "urn:o-ran-sc:params:xml:ns:yang:nts:x-ran";
  prefix nts-x-ran;

  import nts-common {
    prefix ntsc;
  }

  organization
    "O-RAN-SC";
  contact
    " Web: <https://wiki.o-ran-sc.org/display/SIM/SIM>
        Editors:
        Alex Stancu <mailto:alexandru.stancu@highstreet-technologies.com>
        Adrian Lita <mailto:adrian.lita@highstreet-technologies.com>
        Martin Skorupski <mailto:martin.skorupski@highstreet-technologies.com>";
  description
    "This module contains YANG definitions for the Network Topology Simulator - X-RAN extensions.";

  revision 2020-11-30 {
    description
      "Cleared revision for nts-common import.";
    reference
      "X-RAN implementation";
  }
  revision 2020-10-26 {
    description
      "Initial revision for the Network Topology Simulator - Next Generation";
    reference
      "X-RAN implementation";
  }

  identity NTS_FUNCTION_TYPE_X_RAN {
    base ntsc:NTS_FUNCTION_TYPE_BASE;
    description
      "The simulated device implements X-RAN YANG models.";
    reference
      "nts-ng-x-ran";
  }
}
