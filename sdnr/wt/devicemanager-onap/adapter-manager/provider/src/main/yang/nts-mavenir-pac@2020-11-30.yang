module nts-mavenir-pac {
  yang-version 1.1;
  namespace "urn:o-ran-sc:params:xml:ns:yang:nts:mavenir";
  prefix nts-mvn;

  import nts-common {
    prefix ntsc;
  }

  organization
    "O-RAN-SC";
  contact
    " Web: <https://wiki.o-ran-sc.org/display/SIM/SIM>
        Editors:
        Alex Stancu <mailto:alexandru.stancu@highstreet-technologies.com>
        Adrian Lita <mailto:adrian.lita@highstreet-technologies.com>
        Martin Skorupski <mailto:martin.skorupski@highstreet-technologies.com>";
  description
    "This module contains YANG definitions for the Network Topology Simulator - Mavenir extensions.";

  revision 2020-11-30 {
    description
      "Cleared revision for nts-common import.";
    reference
      "Mavenir implemenation.";
  }
  revision 2020-09-07 {
    description
      "Initial revision for the Network Topology Simulator - Next Generation";
    reference
      "Mavenir implemenation.";
  }

  identity NTS_FUNCTION_TYPE_MAVENIR_ENBCU {
    base ntsc:NTS_FUNCTION_TYPE_BASE;
    description
      "The simulated network function implements a Mavenir eNodeB-CU YANG model.";
    reference
      "nts-ng-mavenir-enbcu";
  }

  identity NTS_FUNCTION_TYPE_MAVENIR_ENBDU {
    base ntsc:NTS_FUNCTION_TYPE_BASE;
    description
      "The simulated network function implements a Mavenir eNodeB-DU YANG model.";
    reference
      "nts-ng-mavenir-enbdu";
  }
}
