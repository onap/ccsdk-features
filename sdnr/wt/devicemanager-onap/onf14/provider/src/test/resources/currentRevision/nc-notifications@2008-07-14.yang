module nc-notifications {
  namespace "urn:ietf:params:xml:ns:netmod:notification";
  prefix manageEvent;

  import ietf-yang-types {
    prefix yang;
  }
  import notifications {
    prefix ncEvent;
  }

  organization
    "IETF NETCONF WG";
  contact
    "netconf@ietf.org";
  description
    "Conversion of the 'manageEvent' XSD in the NETCONF
     Notifications RFC.";
  reference
    "RFC 5277";

  revision 2008-07-14 {
    description
      "RFC 5277 version.";
  }

  container netconf {
    config false;
    description
      "Top-level element in the notification namespace";
    container streams {
      description
        "The list of event streams supported by the system. When
         a query is issued, the returned set of streams is
         determined based on user privileges.";
      list stream {
        key "name";
        min-elements 1;
        description
          "Stream name, description and other information.";
        leaf name {
          type ncEvent:streamNameType;
          description
            "The name of the event stream. If this is the default
             NETCONF stream, this must have the value 'NETCONF'.";
        }
        leaf description {
          type string;
          mandatory true;
          description
            "A description of the event stream, including such
             information as the type of events that are sent over
             this stream.";
        }
        leaf replaySupport {
          type boolean;
          mandatory true;
          description
            "A description of the event stream, including such
             information as the type of events that are sent over
             this stream.";
        }
        leaf replayLogCreationTime {
          type yang:date-and-time;
          description
            "The timestamp of the creation of the log used to support
             the replay function on this stream. Note that this might
             be earlier then the earliest available notification in
             the log. This object is updated if the log resets for
             some reason.  This object MUST be present if replay is
             supported.";
        }
        leaf replayLogAgedTime {
          type yang:date-and-time;
          description
            "The timestamp of the last notification
             aged out of the log. This
             object MUST be present if replay is
             supported and any notifications
             have been aged out of the log.";
        }
      }
    }
  }

  notification replayComplete {
    description
      "This notification is sent to signal the end of a replay
       portion of a subscription.";
  }
  notification notificationComplete {
    description
      "This notification is sent to signal the end of a notification
       subscription. It is sent in the case that stopTime was
       specified during the creation of the subscription..";
  }
}
