module dmi-registry {

  yang-version 1.1;

  namespace "org:onap:cps:ncmp";

  prefix dmi-reg;

  organization "Ericsson Software Tech.";

  contact "rahul.tyagi@est.tech";

  revision "2021-05-20" {
    description
    "Initial Version";
  }

  container dmi-registry {

    list cm-handle {

      key "id";

      leaf id {
        type string;
      }

      leaf dmi-service-name {
        type string;
      }

      list additional-properties {

        key "name";

        leaf name {
          type string;
        }

        leaf value {
          type string;
        }
      }
    }
  }
}
