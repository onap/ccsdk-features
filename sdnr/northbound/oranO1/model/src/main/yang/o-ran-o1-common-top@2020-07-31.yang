module o-ran-o1-common-top {

  yang-version 1.1;
  namespace "urn:o-ran:o1-common-top:1";
  prefix "o-ran-o1-top";

  organization "O-RAN Alliance";
  contact "www.o-ran.org";
  description
    "Common base for all O-RAN O1 managed function IOCs.
    
    Copyright 2020 the O-RAN Alliance.
    
    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.
    
    Redistribution and use in source and binary forms, with or without
    modification, are permitted provided that the following conditions are met:
    
    * Redistributions of source code must retain the above copyright notice,
      this list of conditions and the above disclaimer.
    * Redistributions in binary form must reproduce the above copyright notice,
      this list of conditions and the above disclaimer in the documentation
      and/or other materials provided with the distribution.
    * Neither the Members of the o-RAN Alliance nor the names of its
      contributors may be used to endorse or promote products derived from
      this software without specific prior written permission.";

  revision 2020-07-31 {
    description "version 2.0.0: initial revision";
    reference "O-RAN-WG1.O1-Interface-v02.00";
  }

  grouping o-top {
    description "Abstract class supplying a naming attribute";
    reference "O-RAN-WG1.O1-Interface-v02.00";

    leaf name {
      type string { length "1..255"; }
      description "A name that is unique that identifies a function instance.
        This name may be used in fault management to refer to a fault source
        or affected object";
    }

  }

}
