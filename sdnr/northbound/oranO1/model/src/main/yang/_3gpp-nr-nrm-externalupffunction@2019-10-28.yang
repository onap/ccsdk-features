module _3gpp-nr-nrm-externalupffunction {
  yang-version 1.1;
  namespace "urn:3gpp:sa5:_3gpp-nr-nrm-externalupffunction";
  prefix "extupf3gpp";
    
  import _3gpp-common-managed-function { prefix mf3gpp; }
  import _3gpp-common-subnetwork { prefix subnet3gpp; }
  import _3gpp-nr-nrm-nrnetwork { prefix nrnet3gpp; }
  import _3gpp-common-top { prefix top3gpp; }

  organization "3GPP SA5";
  description "Defines the YANG mapping of the ExternalUPFFunction Information
    Object Class (IOC) that is part of the NR Network Resource Model (NRM).";
  reference "3GPP TS 28.541 5G Network Resource Model (NRM)";

  revision 2019-10-28 { reference S5-193518 ; }
  revision 2019-06-17 {
    description "Initial revision";
  }

  grouping ExternalUPFFunctionGrp {
    description "Represents the ExternalUPFFunction IOC.";
    reference "3GPP TS 28.541";
    uses mf3gpp:ManagedFunctionGrp;
  }

  grouping ExternalUPFFunctionWrapper {
    list ExternalUPFFunction {
      description "Represents the properties, known by the management
        function, of a UPFFunction managed by another management
        function.";
      reference "3GPP TS 28.541";
      key id;
      uses top3gpp:Top_Grp;
      container attributes {
        uses ExternalUPFFunctionGrp;
      }
      uses mf3gpp:ManagedFunctionContainedClasses;
    }
  } 
  
  augment "/subnet3gpp:SubNetwork" {
    if-feature subnet3gpp:ExternalsUnderSubNetwork ;
    uses ExternalUPFFunctionWrapper;
  }

  augment "/nrnet3gpp:NRNetwork" {
    if-feature nrnet3gpp:ExternalsUnderNRNetwork;
    uses ExternalUPFFunctionWrapper;
  }
}
