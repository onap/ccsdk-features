module _3gpp-nr-nrm-externalservinggwfunction {
  yang-version 1.1;
  namespace "urn:3gpp:sa5:_3gpp-nr-nrm-externalservinggwfunction";
  prefix "extservgw3gpp";
    
  import _3gpp-common-managed-function { prefix mf3gpp; }
  import _3gpp-common-subnetwork { prefix subnet3gpp; }
  import _3gpp-nr-nrm-eutranetwork { prefix eutranet3gpp; }
  import _3gpp-common-top { prefix top3gpp; }

  organization "3GPP SA5";
  description "Defines the YANG mapping of the ExternalServingGWFunction
    Information Object Class (IOC) that is part of the NR Network Resource
    Model (NRM).";
  reference "3GPP TS 28.541 5G Network Resource Model (NRM)";

  revision 2019-10-28 { reference S5-193518 ; }
  revision 2019-06-17 {
    description "Initial revision";
  }

  grouping ExternalServingGWFunctionGrp {
    description "Represents the ExternalServingGWFunction IOC.";
    reference "3GPP TS 28.541";
    uses mf3gpp:ManagedFunctionGrp;
  }

  grouping ExternalServingGWFunctionWrapper {
    list ExternalServingGWFunction {
      description "Represents the properties, known by the management
        function, of a ServingGWFunction managed by another management
        function.";
      reference "3GPP TS 28.658";
      key id;
      uses top3gpp:Top_Grp;
      container attributes {
        uses ExternalServingGWFunctionGrp;
      }
      uses mf3gpp:ManagedFunctionContainedClasses;
    }
  } 
  
  augment "/subnet3gpp:SubNetwork" {
    if-feature subnet3gpp:ExternalsUnderSubNetwork ;
    uses ExternalServingGWFunctionWrapper;
  }

  augment "/eutranet3gpp:EUtraNetwork" {
    if-feature eutranet3gpp:ExternalsUnderEUtraNetwork;
    uses ExternalServingGWFunctionWrapper;
  }
}
