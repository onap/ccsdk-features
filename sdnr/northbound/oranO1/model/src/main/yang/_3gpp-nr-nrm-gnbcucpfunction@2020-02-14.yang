module _3gpp-nr-nrm-gnbcucpfunction {
  yang-version 1.1;
  namespace "urn:3gpp:sa5:_3gpp-nr-nrm-gnbcucpfunction";
  prefix "gnbcucp3gpp";
    
  import _3gpp-common-yang-types { prefix types3gpp; }
  import _3gpp-common-managed-function { prefix mf3gpp; }
  import _3gpp-common-managed-element { prefix me3gpp; }
  import _3gpp-common-top { prefix top3gpp; }
  import _3gpp-nr-nrm-rrmpolicy { prefix nrrrmpolicy3gpp; }

  organization "3GPP SA5";
  description "Defines the YANG mapping of the GNBCUCPFunction Information 
    Object Class (IOC) that is part of the NR Network Resource Model (NRM).";
  reference "3GPP TS 28.541 5G Network Resource Model (NRM)";

  revision 2020-02-14 { reference S5-20XXXX ; }
  revision 2019-10-28 { reference S5-193518 ; }
  revision 2019-06-17 {
    description "Initial revision";
  }
 
  grouping GNBCUCPFunctionGrp {
    description "Represents the GNBCUCPFunction IOC.";
    reference "3GPP TS 28.541";
    uses mf3gpp:ManagedFunctionGrp;
    uses nrrrmpolicy3gpp:RRMPolicy_Grp;

    leaf gNBId {
      description "Identifies a gNB within a PLMN. The gNB Identifier (gNB ID)
        is part of the NR Cell Identifier (NCI) of the gNB cells.";
      reference "gNB ID in 3GPP TS 38.300, Global gNB ID in 3GPP TS 38.413";
      mandatory true;
      type int64 { range "0..4294967295"; }
    }

    leaf gNBIdLength {
      description "Indicates the number of bits for encoding the gNB ID.";
      reference "gNB ID in 3GPP TS 38.300, Global gNB ID in 3GPP TS 38.413";
      mandatory true;
      type int32 { range "22..32"; }
    }

    leaf gNBCUName {
      description "Identifies the Central Unit of an gNB.";
      reference "3GPP TS 38.473";
      mandatory true;
      type string { length "1..150"; }
    }

    list pLMNId {
      description "The PLMN identifier to be used as part of the global RAN
        node identity.";
      key "mcc mnc";
      min-elements 1;
      max-elements 1;
      uses types3gpp:PLMNId;
    } 

    leaf-list x2BlackList {
      type types3gpp:DistinguishedName;
      description "List of nodes to which X2 connections are prohibited.";
    }

    leaf-list x2WhiteList {
      type types3gpp:DistinguishedName;
      description "List of nodes to which X2 connections are enforced.";
    }

    leaf-list xnBlackList {
      type types3gpp:DistinguishedName;
      description "List of nodes to which Xn connections are prohibited.";
    }

    leaf-list xnWhiteList {
      type types3gpp:DistinguishedName;
      description "List of nodes to which X2 connections are enforced.";
    }

    leaf-list x2XnHOBlackList {
      type types3gpp:DistinguishedName;
      description "List of nodes to which handovers over X2 or Xn are prohibited.";
    }
  }

  augment "/me3gpp:ManagedElement" {

    list GNBCUCPFunction {
      description "Represents the logical function CU-CP of gNB and en-gNB.";
      reference "3GPP TS 28.541";
      key id;
      uses top3gpp:Top_Grp;
      container attributes {    
        uses GNBCUCPFunctionGrp;
      }
      uses mf3gpp:ManagedFunctionContainedClasses;
    }
  }
}
