module o-ran-o1-external-o-enb-function {

  yang-version 1.1;
  namespace "urn:o-ran:o-ran-o1-external-o-enb-function";
  prefix "o-ran-o1-extenb";

  import _3gpp-common-managed-element { prefix me3gpp; }
  import _3gpp-nr-nrm-externalgnbcucpfunction { prefix extgnbcucp3gpp; }
  import _3gpp-nr-nrm-gnbcucpfunction { prefix gnbcucp3gpp; }
  import o-ran-o1-eutranetwork { prefix o-ran-o1-eutranet; }

  organization "O-RAN Alliance";
  contact "www.o-ran.org";
  description
    "Augments the ENBFunction IOC to be placed the GNBCUCPFunction IOC.

    Copyright 2020 the O-RAN Alliance.
    
    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.
    
    Redistribution and use in source and binary forms, with or without
    modification, are permitted provided that the following conditions are met:
    
    * Redistributions of source code must retain the above copyright notice,
      this list of conditions and the above disclaimer.
    * Redistributions in binary form must reproduce the above copyright notice,
      this list of conditions and the above disclaimer in the documentation
      and/or other materials provided with the distribution.
    * Neither the Members of the o-RAN Alliance nor the names of its
      contributors may be used to endorse or promote products derived from
      this software without specific prior written permission.";

  revision 2020-07-31 {
    description "version 2.0.0: initial revision";
    reference "O-RAN-WG1.O1-Interface-v02.00";
  }


  augment "/me3gpp:ManagedElement/gnbcucp3gpp:GNBCUCPFunction/o-ran-o1-eutranet:o-eutra-network" {
    if-feature o-ran-o1-eutranet:o-ran-o1-eutra-externals;
    uses extgnbcucp3gpp:ExternalGNBCUCPFunctionWrapper;
    description
      "Adds 'eutra externals' to 'eutra network'.";
  }
}
