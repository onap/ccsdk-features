module o-ran-o1-eutranetwork {
  yang-version 1.1;
  namespace "urn:o-ran:o-ran-o1-eutranetwork";
  prefix "o-ran-o1-eutranet";

  import _3gpp-common-managed-function { prefix mf3gpp; }
  import _3gpp-common-managed-element { prefix me3gpp; }
  import _3gpp-common-top { prefix top3gpp; }
  import _3gpp-nr-nrm-gnbcucpfunction { prefix gnbcucp3gpp; }
  import o-ran-o1-common-top { prefix o-ran-o1-top; }

  organization "O-RAN Alliance";
  contact "www.o-ran.org";
  description
    "Augments the EUtraNetwork IOC to be placed the GNBCUCPFunction IOC.

    Copyright 2020 the O-RAN Alliance.
    
    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.
    
    Redistribution and use in source and binary forms, with or without
    modification, are permitted provided that the following conditions are met:
    
    * Redistributions of source code must retain the above copyright notice,
      this list of conditions and the above disclaimer.
    * Redistributions in binary form must reproduce the above copyright notice,
      this list of conditions and the above disclaimer in the documentation
      and/or other materials provided with the distribution.
    * Neither the Members of the o-RAN Alliance nor the names of its
      contributors may be used to endorse or promote products derived from
      this software without specific prior written permission.";

  revision 2020-07-31 {
    description "version 2.0.0: initial revision";
    reference "O-RAN-WG1.O1-Interface-v02.00";
  }


  feature o-ran-o1-eutra-externals{
    description "Classes representing external LTE entities, in particular ExternalENBFunction and ExternalEUtranCellFDD/TDD,
      are placed under a O-EUtraNetwork IOC placed under the 3GPP defined GNBCUCPFunction IOC.";
  }

  grouping o-eutra-network-grp {
    description "Represents the O-EUtra-Network IOC.";
    uses gnbcucp3gpp:GNBCUCPFunctionGrp;
  }

  augment "/me3gpp:ManagedElement/gnbcucp3gpp:GNBCUCPFunction" {
    if-feature o-ran-o1-eutra-externals;  
    list o-eutra-network{
      key id;
      uses top3gpp:Top_Grp;
      uses o-ran-o1-top:o-top;
      uses mf3gpp:ManagedFunctionContainedClasses;
      container attributes {
        uses o-eutra-network-grp;
        description "Groups attributes for eutra network.";
      }
      description "A o-eutra-network containing external LTE entities.";
      reference "O-RAN-WG1.O1-Interface-v02.00";
    }
    description "Adds eutra networks to gNB CU CP.";
  }
}
