module _3gpp-nr-nrm-nrnetwork {
  yang-version 1.1;
  namespace "urn:3gpp:sa5:_3gpp-nr-nrm-nrnetwork";
  prefix "nrnet3gpp";

  import _3gpp-common-subnetwork { prefix subnet3gpp; }
  import _3gpp-common-top { prefix top3gpp; }

  organization "3GPP SA5";
  description "Defines the YANG mapping of the NRNetwork Information Object
    Class (IOC) that is part of the NR Network Resource Model (NRM).";
  reference "3GPP TS 28.541 5G Network Resource Model (NRM)";

  revision 2019-06-17 {
    description "Initial revision";
  }

  feature ExternalsUnderNRNetwork {
    description "Classes representing external entities like NRFrequency, 
      ExternalGNBCUCPFunction, ExternalGNBDUFunction 
      are contained under a NRNetwork list/class.";
  }

  grouping NRNetworkGrp {
    description "Represents the NRNetwork IOC.";
    reference "3GPP TS 28.541";
    uses subnet3gpp:SubNetworkGrp;
  }

  list NRNetwork {
    description "A subnetwork containing gNB external NR entities.";
      reference "3GPP TS 28.541";
    key id;
    uses top3gpp:Top_Grp;
    container attributes {
      uses NRNetworkGrp;
    }
  }
}
