module _3gpp-nr-nrm-eutranfrequency {
  yang-version 1.1;
  namespace "urn:3gpp:sa5:_3gpp-nr-nrm-eutranfrequency";
  prefix "eutraneteutranfreq3gpp";

  import _3gpp-common-managed-function { prefix mf3gpp; }
  import _3gpp-nr-nrm-eutranetwork { prefix eutranet3gpp; }
  import _3gpp-common-subnetwork { prefix subnet3gpp; }
  import _3gpp-common-top { prefix top3gpp; }

  organization "3GPP SA5";
  description "Defines the YANG mapping of the EUtranFrequency Information
    Object Class (IOC), that is part of the NR Network Resource Model (NRM).";
  reference "3GPP TS 28.541 5G Network Resource Model (NRM),
    3GPP TS 28.658 (E-UTRAN) Network Resource Model (NRM)";

  revision 2019-10-28 { reference S5-193518 ; }
  revision 2019-06-17 {
    description "Initial revision";
  }

  grouping EUtranFrequencyGrp {
    description "Represents the EUtranFrequency IOC.";
    reference "3GPP TS 28.541";
    uses mf3gpp:ManagedFunctionGrp;

    leaf earfcnDL {
      description "Specifies the channel number for the central DL frequency.";
      reference "3GPP TS 36.101";
      mandatory true;
      type uint32 { range "0..262143"; }
    }

    leaf-list multiBandInfoListEutra {
      description "List of additional frequency bands the frequency belongs to.";
      config false;
      min-elements 0;
      type uint16 { range "1..256"; }
    }
  }

  grouping EUtranFrequencyWrapper {
    list EUtranFrequency {
      description "Represents certain E-UTRAN frequency properties.";
      reference "3GPP TS 28.658";
      key id;
      uses top3gpp:Top_Grp;
      container attributes {
        uses EUtranFrequencyGrp;
      }
      uses mf3gpp:ManagedFunctionContainedClasses;
    }
  } 
  
  augment "/subnet3gpp:SubNetwork" {
    if-feature subnet3gpp:ExternalsUnderSubNetwork ;
    uses EUtranFrequencyWrapper ;
  }

  augment "/eutranet3gpp:EUtraNetwork" {
    if-feature eutranet3gpp:ExternalsUnderEUtraNetwork;
    uses EUtranFrequencyWrapper ;
  }
}
