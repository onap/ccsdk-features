module o-ran-o1-o-sector-carrier {

  yang-version 1.1;
  namespace "urn:o-ran:o1-nrsectorcarrier:1";
  prefix "o-ran-o1-nrsectcarr";

  import _3gpp-common-managed-function { prefix mf3gpp; }
  import _3gpp-common-managed-element { prefix me3gpp; }
  import _3gpp-common-top { prefix top3gpp; }
  import _3gpp-nr-nrm-nrsectorcarrier { prefix nrsectcarr3gpp; }
  import o-ran-o1-common-top { prefix o-ran-o1-top; }
  import o-ran-o1-o-ru-function { prefix o-ran-o1-rufunc; }

  organization "O-RAN Alliance";
  contact "www.o-ran.org";
  description
    "Augments the O-RU-Function of the O-RAN O1-Interface Model with the 3GPP NRSectorCarrier IOC.
    
    Copyright 2020 the O-RAN Alliance.
    
    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.
    
    Redistribution and use in source and binary forms, with or without
    modification, are permitted provided that the following conditions are met:
    
    * Redistributions of source code must retain the above copyright notice,
      this list of conditions and the above disclaimer.
    * Redistributions in binary form must reproduce the above copyright notice,
      this list of conditions and the above disclaimer in the documentation
      and/or other materials provided with the distribution.
    * Neither the Members of the o-RAN Alliance nor the names of its
      contributors may be used to endorse or promote products derived from
      this software without specific prior written permission.";

  revision 2020-07-31 {
    description "version 2.0.0: initial revision";
    reference "O-RAN-WG1.O1-Interface-v02.00";
  }

  augment "/me3gpp:ManagedElement/o-ran-o1-rufunc:o-ru-function" {
    list o-sector-carrier {
      key id;
      uses top3gpp:Top_Grp;
      uses o-ran-o1-top:o-top;
      uses mf3gpp:ManagedFunctionContainedClasses;
      container attributes {
        uses nrsectcarr3gpp:NRSectorCarrierGrp;
        description
         "Groups all the section carrier attibutes.";
      }
      description "Represents the resources of each transmission point included in the cell.";
      reference "3GPP TS 28.541";
    }
    description 
      "Adds a list of sector carriers to O-RU function.";
  }
}
