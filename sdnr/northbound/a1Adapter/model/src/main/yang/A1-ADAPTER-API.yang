//-
// ============LICENSE_START=======================================================
//  Copyright (C) 2020 Nordix Foundation.
// ================================================================================
// Licensed under the Apache License, Version 2.0 (the "License");
// you may not use this file except in compliance with the License.
// You may obtain a copy of the License at
//
//      http://www.apache.org/licenses/LICENSE-2.0
//
// Unless required by applicable law or agreed to in writing, software
// distributed under the License is distributed on an "AS IS" BASIS,
// WITHOUT WARRANTIES OR CONDITIONS OF ANY KIND, either express or implied.
// See the License for the specific language governing permissions and
// limitations under the License.
//
// SPDX-License-Identifier: Apache-2.0
// ============LICENSE_END=========================================================
//
module A1-ADAPTER-API {

    namespace "org:onap:a1-adapter";

    prefix a1-adapter-api;

    import ietf-inet-types {
        prefix "inet";
        revision-date "2013-07-15";
    }

    import ietf-yang-types {
        prefix yang;
    }

    revision "2020-01-22" {
        description
          "A1 adapter";
    }

    rpc putA1Policy {
        input {
            leaf near-rt-ric-url {
                type inet:uri;
            }
            leaf body {
                type string;
            }
        }
        output {
            leaf body {
                type string;
            }
            leaf http-status {
                type int32;
            }
        }
    }

    rpc getA1Policy {
        input {
            leaf near-rt-ric-url {
                type inet:uri;
            }
        }
        output {
            leaf body {
                type string;
            }
            leaf http-status {
                type int32;
            }
        }
    }

    rpc getA1PolicyStatus {
        input {
            leaf near-rt-ric-url {
                type inet:uri;
            }
        }
        output {
            leaf body {
                type string;
            }
            leaf http-status {
                type int32;
            }
        }
    }

    rpc getA1PolicyType {
        input {
            leaf near-rt-ric-url {
                type inet:uri;
            }
        }
        output {
            leaf body {
                type string;
            }
            leaf http-status {
                type int32;
            }
        }
    }

    rpc deleteA1Policy {
        input {
            leaf near-rt-ric-url {
                type inet:uri;
            }
        }
        output {
            leaf body {
                type string;
            }
            leaf http-status {
                type int32;
            }
        }
    }
}
